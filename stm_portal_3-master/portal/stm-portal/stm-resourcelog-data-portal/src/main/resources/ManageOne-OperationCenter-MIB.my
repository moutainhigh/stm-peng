--
-- HUAWEI-OperationCenter-MIB.my
-- MIB generated by MG-SOFT Visual MIB Builder version 3.0 Build 349
-- 
--

	HUAWEI-MONITOR-MIB DEFINITIONS ::= BEGIN
 
		IMPORTS
			enterprises, Integer32, OBJECT-TYPE			
				FROM SNMPv2-SMI;
	
	
--
-- Node definitions
--
	
		-- 1.3.6.1.4.1.2011
		huawei OBJECT IDENTIFIER ::= { enterprises 2011 }

		
		-- 1.3.6.1.4.1.2011.2
		it_product_line OBJECT IDENTIFIER ::= { huawei 2 }

		
		-- 1.3.6.1.4.1.2011.2.288
		operationCenter OBJECT IDENTIFIER ::= { it_product_line 288 }

		
		-- 1.3.6.1.4.1.2011.2.288.1
		alarmTable OBJECT-TYPE
			SYNTAX SEQUENCE OF AlarmEntry
			MAX-ACCESS not-accessible
			STATUS current
			DESCRIPTION
				"Description."
			::= { operationCenter 1 }

		
		-- 1.3.6.1.4.1.2011.2.288.1.1
		alarmEntry OBJECT-TYPE
			SYNTAX AlarmEntry
			MAX-ACCESS not-accessible
			STATUS current
			DESCRIPTION
				"Description."
			INDEX { alarm_sn }
			::= { alarmTable 1 }

		
		AlarmEntry ::=
			SEQUENCE { 
				alarm_sn
					OCTET STRING,
				alarm_id
					OCTET STRING,
				alarm_name
					OCTET STRING,
				severity
					INTEGER,
				first_report_time
					OCTET STRING,
				last_report_time
					OCTET STRING,
				occur_times
					INTEGER,
				object_code
					OCTET STRING,
				model
					OCTET STRING,
				object_name
					OCTET STRING,
				object_ciid
					OCTET STRING,
				zone_code
					OCTET STRING,
				customer_code
					OCTET STRING,
				data_center_code
					OCTET STRING,
				cluster_code
					OCTET STRING,
				machine_room_code
					OCTET STRING,
				pool_mag_code
					OCTET STRING,
				alarm_monitor_sys_code
					OCTET STRING,
				perf_monitor_sys_code
					OCTET STRING,
			    service_group_code
					OCTET STRING,
				user_define_attr1
					OCTET STRING,
				user_define_attr2
					OCTET STRING,
				province_code
					OCTET STRING,
				logic_zone_code
					OCTET STRING,
				phydc_code
					OCTET STRING,
				object_type1
					OCTET STRING,
				object_type
					OCTET STRING,
				old_additional
					OCTET STRING,
				remark
					OCTET STRING,
				manufacturer
					OCTET STRING,
				old_alarm_source_obj_ip
					OCTET STRING,
				old_alarm_reason
					OCTET STRING,
				old_reason_located_info
					OCTET STRING,
				type
					INTEGER,
				old_alarm_id
					OCTET STRING
			 }

		-- 1.3.6.1.4.1.2011.2.288.1.1.1
		alarm_sn OBJECT-TYPE
			SYNTAX OCTET STRING
			MAX-ACCESS read-only
			STATUS current
			DESCRIPTION
				"Description."
			::= { alarmEntry 1 }

		
		-- 1.3.6.1.4.1.2011.2.288.1.1.2
		alarm_id OBJECT-TYPE
			SYNTAX OCTET STRING
			MAX-ACCESS read-only
			STATUS current
			DESCRIPTION
				"Description."
			::= { alarmEntry 2 }

		
		-- 1.3.6.1.4.1.2011.2.288.1.1.3
		alarm_name OBJECT-TYPE
			SYNTAX OCTET STRING
			MAX-ACCESS read-only
			STATUS current
			DESCRIPTION
				"Description."
			::= { alarmEntry 3 }

		
		-- 1.3.6.1.4.1.2011.2.288.1.1.4
		severity OBJECT-TYPE
			SYNTAX INTEGER
			MAX-ACCESS read-only
			STATUS current
			DESCRIPTION
				"Description."
			::= { alarmEntry 4 }

		
		-- 1.3.6.1.4.1.2011.2.288.1.1.5
		first_report_time OBJECT-TYPE
			SYNTAX OCTET STRING
			MAX-ACCESS read-only
			STATUS current
			DESCRIPTION
				"Description."
			::= { alarmEntry 5 }

		
		-- 1.3.6.1.4.1.2011.2.288.1.1.6
		last_report_time OBJECT-TYPE
			SYNTAX OCTET STRING
			MAX-ACCESS read-only
			STATUS current
			DESCRIPTION
				"Description."
			::= { alarmEntry 6 }

		
		-- 1.3.6.1.4.1.2011.2.288.1.1.7
		occur_times OBJECT-TYPE
			SYNTAX INTEGER
			MAX-ACCESS read-only
			STATUS current
			DESCRIPTION
				"Description."
			::= { alarmEntry 7 }

		
		-- 1.3.6.1.4.1.2011.2.288.1.1.8
		object_code OBJECT-TYPE
			SYNTAX OCTET STRING
			MAX-ACCESS read-only
			STATUS current
			DESCRIPTION
				"Description."
			::= { alarmEntry 8 }
			
		
		-- 1.3.6.1.4.1.2011.2.288.1.1.9
		model OBJECT-TYPE
			SYNTAX OCTET STRING
			MAX-ACCESS read-only
			STATUS current
			DESCRIPTION
				"Description."
			::= { alarmEntry 9 }

		
		-- 1.3.6.1.4.1.2011.2.288.1.1.10
		object_name OBJECT-TYPE
			SYNTAX OCTET STRING
			MAX-ACCESS read-only
			STATUS current
			DESCRIPTION
				"Description."
			::= { alarmEntry 10 }

		
		-- 1.3.6.1.4.1.2011.2.288.1.1.15
		object_ciid OBJECT-TYPE
			SYNTAX OCTET STRING
			MAX-ACCESS read-only
			STATUS current
			DESCRIPTION
				"Description."
			::= { alarmEntry 15 }

		
		-- 1.3.6.1.4.1.2011.2.288.1.1.18
		zone_code OBJECT-TYPE
			SYNTAX OCTET STRING
			MAX-ACCESS read-only
			STATUS current
			DESCRIPTION
				"Description."
			::= { alarmEntry 18 }

		
		-- 1.3.6.1.4.1.2011.2.288.1.1.19
		customer_code OBJECT-TYPE
			SYNTAX OCTET STRING
			MAX-ACCESS read-only
			STATUS current
			DESCRIPTION
				"Description."
			::= { alarmEntry 19 }

		
		-- 1.3.6.1.4.1.2011.2.288.1.1.20
		data_center_code OBJECT-TYPE
			SYNTAX OCTET STRING
			MAX-ACCESS read-only
			STATUS current
			DESCRIPTION
				"Description."
			::= { alarmEntry 20 }

		
		-- 1.3.6.1.4.1.2011.2.288.1.1.21
		cluster_code OBJECT-TYPE
			SYNTAX OCTET STRING
			MAX-ACCESS read-only
			STATUS current
			DESCRIPTION
				"Description."
			::= { alarmEntry 21 }

		
		-- 1.3.6.1.4.1.2011.2.288.1.1.22
		machine_room_code OBJECT-TYPE
			SYNTAX OCTET STRING
			MAX-ACCESS read-only
			STATUS current
			DESCRIPTION
				"Description."
			::= { alarmEntry 22 }

		
		-- 1.3.6.1.4.1.2011.2.288.1.1.23
		pool_mag_code OBJECT-TYPE
			SYNTAX OCTET STRING
			MAX-ACCESS read-only
			STATUS current
			DESCRIPTION
				"Description."
			::= { alarmEntry 23 }

		
		-- 1.3.6.1.4.1.2011.2.288.1.1.24
		alarm_monitor_sys_code OBJECT-TYPE
			SYNTAX OCTET STRING
			MAX-ACCESS read-only
			STATUS current
			DESCRIPTION
				"Description."
			::= { alarmEntry 24 }
			
		
		-- 1.3.6.1.4.1.2011.2.288.1.1.25
		perf_monitor_sys_code OBJECT-TYPE
			SYNTAX OCTET STRING
			MAX-ACCESS read-only
			STATUS current
			DESCRIPTION
				"Description."
			::= { alarmEntry 25 }
			
		
		-- 1.3.6.1.4.1.2011.2.288.1.1.26
		service_group_code OBJECT-TYPE
			SYNTAX OCTET STRING
			MAX-ACCESS read-only
			STATUS current
			DESCRIPTION
				"Description."
			::= { alarmEntry 26 }

		
		-- 1.3.6.1.4.1.2011.2.288.1.1.27
		user_define_attr1 OBJECT-TYPE
			SYNTAX OCTET STRING
			MAX-ACCESS read-only
			STATUS current
			DESCRIPTION
				"Description."
			::= { alarmEntry 27 }

		
		-- 1.3.6.1.4.1.2011.2.288.1.1.28
		user_define_attr2 OBJECT-TYPE
			SYNTAX OCTET STRING
			MAX-ACCESS read-only
			STATUS current
			DESCRIPTION
				"Description."
			::= { alarmEntry 28 }
			
			
		-- 1.3.6.1.4.1.2011.2.288.1.1.29
		province_code OBJECT-TYPE
			SYNTAX OCTET STRING
			MAX-ACCESS read-only
			STATUS current
			DESCRIPTION
				"Description."
			::= { alarmEntry 29 }

		
		-- 1.3.6.1.4.1.2011.2.288.1.1.31
		logic_zone_code OBJECT-TYPE
			SYNTAX OCTET STRING
			MAX-ACCESS read-only
			STATUS current
			DESCRIPTION
				"Description."
			::= { alarmEntry 31 }

		
		-- 1.3.6.1.4.1.2011.2.288.1.1.32
		phydc_code OBJECT-TYPE
			SYNTAX OCTET STRING
			MAX-ACCESS read-only
			STATUS current
			DESCRIPTION
				"Description."
			::= { alarmEntry 32 }

		
		-- 1.3.6.1.4.1.2011.2.288.1.1.34
		object_type1 OBJECT-TYPE
			SYNTAX OCTET STRING
			MAX-ACCESS read-only
			STATUS current
			DESCRIPTION
				"Description."
			::= { alarmEntry 34 }
						
			
		-- 1.3.6.1.4.1.2011.2.288.1.1.35
		object_type OBJECT-TYPE
			SYNTAX OCTET STRING
			MAX-ACCESS read-only
			STATUS current
			DESCRIPTION
				"Description."
			::= { alarmEntry 35 }

		
		-- 1.3.6.1.4.1.2011.2.288.1.1.36
		old_additional OBJECT-TYPE
			SYNTAX OCTET STRING
			MAX-ACCESS read-only
			STATUS current
			DESCRIPTION
				"Description."
			::= { alarmEntry 36 }

		
		-- 1.3.6.1.4.1.2011.2.288.1.1.37
		remark OBJECT-TYPE
			SYNTAX OCTET STRING
			MAX-ACCESS read-only
			STATUS current
			DESCRIPTION
				"Description."
			::= { alarmEntry 37 }

		
		-- 1.3.6.1.4.1.2011.2.288.1.1.52
		manufacturer OBJECT-TYPE
			SYNTAX OCTET STRING
			MAX-ACCESS read-only
			STATUS current
			DESCRIPTION
				"Description."
			::= { alarmEntry 52 }
									
			
		-- 1.3.6.1.4.1.2011.2.288.1.1.56
		old_alarm_source_obj_ip OBJECT-TYPE
			SYNTAX OCTET STRING
			MAX-ACCESS read-only
			STATUS current
			DESCRIPTION
				"Description."
			::= { alarmEntry 56 }

		
		-- 1.3.6.1.4.1.2011.2.288.1.1.60
		old_alarm_reason OBJECT-TYPE
			SYNTAX OCTET STRING
			MAX-ACCESS read-only
			STATUS current
			DESCRIPTION
				"Description."
			::= { alarmEntry 60 }

		
		-- 1.3.6.1.4.1.2011.2.288.1.1.61
		old_reason_located_info OBJECT-TYPE
			SYNTAX OCTET STRING
			MAX-ACCESS read-only
			STATUS current
			DESCRIPTION
				"Description."
			::= { alarmEntry 61 }

		
		-- 1.3.6.1.4.1.2011.2.288.1.1.62
		type OBJECT-TYPE
			SYNTAX INTEGER
			MAX-ACCESS read-only
			STATUS current
			DESCRIPTION
				"Description."
			::= { alarmEntry 62 }
			
		
		-- 1.3.6.1.4.1.2011.2.288.1.1.63
		old_alarm_id OBJECT-TYPE
			SYNTAX OCTET STRING
			MAX-ACCESS read-only
			STATUS current
			DESCRIPTION
				"Description."
			::= { alarmEntry 63 }
		
		-- 1.3.6.1.4.1.2011.2.288.1.1.0		
		alarmTrap NOTIFICATION-TYPE
			OBJECTS { alarm_sn, alarm_id, alarm_name, severity, first_report_time, 
				last_report_time, occur_times, object_code, model, object_name, 
				object_ciid, zone_code, customer_code, data_center_code, cluster_code, 
				machine_room_code, pool_mag_code, alarm_monitor_sys_code, perf_monitor_sys_code, service_group_code, 
				user_define_attr1, user_define_attr2, province_code, logic_zone_code, phydc_code, 
				object_type1, object_type, old_additional, remark, manufacturer, 
				old_alarm_source_obj_ip, old_alarm_reason, old_reason_located_info, type, old_alarm_id
				 }
			STATUS current
			DESCRIPTION 
				"Description."
			::= { alarmEntry 0 }

		
	
	END

--
-- HUAWEI-OperationCenter-MIB.my
--
