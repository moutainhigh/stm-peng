--
-- HUAWEI-FusionCompute-MIB.my
-- MIB generated by MG-SOFT Visual MIB Builder version 3.0 Build 349
-- Tuesday, November 24, 2015 at 15:28:36
--

	HUAWEI-FusionCompute-MIB DEFINITIONS ::= BEGIN
 
		IMPORTS
			enterprises, OBJECT-TYPE			
				FROM SNMPv2-SMI;
	
	
--
-- Node definitions
--
	
		-- 1.3.6.1.4.1.2011
		huawei OBJECT IDENTIFIER ::= { enterprises 2011 }

		
		-- 1.3.6.1.4.1.2011.2
		it_product_line OBJECT IDENTIFIER ::= { huawei 2 }

		
		-- 1.3.6.1.4.1.2011.2.290
		fusionCompute OBJECT IDENTIFIER ::= { it_product_line 290 }

		
		-- 1.3.6.1.4.1.2011.2.290.1
		alarm OBJECT IDENTIFIER ::= { fusionCompute 1 }

		
		-- 1.3.6.1.4.1.2011.2.290.1.1
		alarmTable OBJECT-TYPE
			SYNTAX SEQUENCE OF AlarmEntry
			MAX-ACCESS not-accessible
			STATUS current
			DESCRIPTION
				"Description."
			::= { alarm 1 }

		
		-- 1.3.6.1.4.1.2011.2.290.1.1.1
		alarmEntry OBJECT-TYPE
			SYNTAX AlarmEntry
			MAX-ACCESS not-accessible
			STATUS current
			DESCRIPTION
				"Description."
			INDEX { alarmindex }
			::= { alarmTable 1 }

		
		AlarmEntry ::=
			SEQUENCE { 
				alarmindex
					OCTET STRING,
				alarmid
					OCTET STRING,
				alarmname
					OCTET STRING,
				resourceid
					OCTET STRING,
				resourceidname
					OCTET STRING,
				moc
					OCTET STRING,
				sn
					OCTET STRING,
				category
					OCTET STRING,
				severity
					OCTET STRING,
				occurtime
					OCTET STRING,
				cleartime
					OCTET STRING,
				cleartype
					OCTET STRING,
				isclear
					OCTET STRING,
				locationinfo
					OCTET STRING,
				additional
					OCTET STRING,
				cause
					OCTET STRING,
				comptype
					OCTET STRING,
				compid
					OCTET STRING,
				compname
					OCTET STRING,
				eventtype
					OCTET STRING
			 }

		-- 1.3.6.1.4.1.2011.2.290.1.1.1.1
		alarmindex OBJECT-TYPE
			SYNTAX OCTET STRING
			MAX-ACCESS read-only
			STATUS current
			DESCRIPTION
				"Description."
			::= { alarmEntry 1 }

		
		-- 1.3.6.1.4.1.2011.2.290.1.1.1.2
		alarmid OBJECT-TYPE
			SYNTAX OCTET STRING
			MAX-ACCESS read-only
			STATUS current
			DESCRIPTION
				"Description."
			::= { alarmEntry 2 }

		
		-- 1.3.6.1.4.1.2011.2.290.1.1.1.3
		alarmname OBJECT-TYPE
			SYNTAX OCTET STRING
			MAX-ACCESS read-only
			STATUS current
			DESCRIPTION
				"Description."
			::= { alarmEntry 3 }

		
		-- 1.3.6.1.4.1.2011.2.290.1.1.1.4
		resourceid OBJECT-TYPE
			SYNTAX OCTET STRING
			MAX-ACCESS read-only
			STATUS current
			DESCRIPTION
				"Description."
			::= { alarmEntry 4 }

		
		-- 1.3.6.1.4.1.2011.2.290.1.1.1.5
		resourceidname OBJECT-TYPE
			SYNTAX OCTET STRING
			MAX-ACCESS read-only
			STATUS current
			DESCRIPTION
				"Description."
			::= { alarmEntry 5 }

		
		-- 1.3.6.1.4.1.2011.2.290.1.1.1.6
		moc OBJECT-TYPE
			SYNTAX OCTET STRING
			MAX-ACCESS read-only
			STATUS current
			DESCRIPTION
				"Description."
			::= { alarmEntry 6 }

		
		-- 1.3.6.1.4.1.2011.2.290.1.1.1.7
		sn OBJECT-TYPE
			SYNTAX OCTET STRING
			MAX-ACCESS read-only
			STATUS current
			DESCRIPTION
				"Description."
			::= { alarmEntry 7 }

		
		-- 1.3.6.1.4.1.2011.2.290.1.1.1.8
		category OBJECT-TYPE
			SYNTAX OCTET STRING
			MAX-ACCESS read-only
			STATUS current
			DESCRIPTION
				"Description."
			::= { alarmEntry 8 }

		
		-- 1.3.6.1.4.1.2011.2.290.1.1.1.9
		severity OBJECT-TYPE
			SYNTAX OCTET STRING
			MAX-ACCESS read-only
			STATUS current
			DESCRIPTION
				"Description."
			::= { alarmEntry 9 }

		
		-- 1.3.6.1.4.1.2011.2.290.1.1.1.10
		occurtime OBJECT-TYPE
			SYNTAX OCTET STRING
			MAX-ACCESS read-only
			STATUS current
			DESCRIPTION
				"Description."
			::= { alarmEntry 10 }

		
		-- 1.3.6.1.4.1.2011.2.290.1.1.1.11
		cleartime OBJECT-TYPE
			SYNTAX OCTET STRING
			MAX-ACCESS read-only
			STATUS current
			DESCRIPTION
				"Description."
			::= { alarmEntry 11 }

		
		-- 1.3.6.1.4.1.2011.2.290.1.1.1.12
		cleartype OBJECT-TYPE
			SYNTAX OCTET STRING
			MAX-ACCESS read-only
			STATUS current
			DESCRIPTION
				"Description."
			::= { alarmEntry 12 }

		
		-- 1.3.6.1.4.1.2011.2.290.1.1.1.13
		isclear OBJECT-TYPE
			SYNTAX OCTET STRING
			MAX-ACCESS read-only
			STATUS current
			DESCRIPTION
				"Description."
			::= { alarmEntry 13 }

		
		-- 1.3.6.1.4.1.2011.2.290.1.1.1.14
		locationinfo OBJECT-TYPE
			SYNTAX OCTET STRING
			MAX-ACCESS read-only
			STATUS current
			DESCRIPTION
				"Description."
			::= { alarmEntry 14 }

		
		-- 1.3.6.1.4.1.2011.2.290.1.1.1.15
		additional OBJECT-TYPE
			SYNTAX OCTET STRING
			MAX-ACCESS read-only
			STATUS current
			DESCRIPTION
				"Description."
			::= { alarmEntry 15 }

		
		-- 1.3.6.1.4.1.2011.2.290.1.1.1.16
		cause OBJECT-TYPE
			SYNTAX OCTET STRING
			MAX-ACCESS read-only
			STATUS current
			DESCRIPTION
				"Description."
			::= { alarmEntry 16 }

		
		-- 1.3.6.1.4.1.2011.2.290.1.1.1.17
		comptype OBJECT-TYPE
			SYNTAX OCTET STRING
			MAX-ACCESS read-only
			STATUS current
			DESCRIPTION
				"Description."
			::= { alarmEntry 17 }

		
		-- 1.3.6.1.4.1.2011.2.290.1.1.1.18
		compid OBJECT-TYPE
			SYNTAX OCTET STRING
			MAX-ACCESS read-only
			STATUS current
			DESCRIPTION
				"Description."
			::= { alarmEntry 18 }

		
		-- 1.3.6.1.4.1.2011.2.290.1.1.1.19
		compname OBJECT-TYPE
			SYNTAX OCTET STRING
			MAX-ACCESS read-only
			STATUS current
			DESCRIPTION
				"Description."
			::= { alarmEntry 19 }

		
		-- 1.3.6.1.4.1.2011.2.290.1.1.1.20
		eventtype OBJECT-TYPE
			SYNTAX OCTET STRING
			MAX-ACCESS read-only
			STATUS current
			DESCRIPTION
				"Description."
			::= { alarmEntry 20 }

		
	
	END

--
-- HUAWEI-FusionCompute-MIB.my
--
